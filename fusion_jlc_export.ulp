#usage "<b>Fusion 360 Electronics / EAGLE JLCPCB Exporter</b>\n"
       "<p>"
       "Exports JLCPCB-ready BOM and CPL CSV files directly from the board editor."
       "<p>"
       "Output files: *_jlc_bom.csv and/or *_jlc_cpl.csv"
       "<p>"
       "<author>Generated by Codex</author>"

// JLC CSV headers required by the upload tool.
string BOM_HEADER = "Comment,Designator,Footprint,LCSC Part #\n";
string BOM_HEADER_EXT = "Comment,Designator,Footprint,LCSC Part #,Part Number,Quantity\n";
string CPL_HEADER = "Designator,Mid X,Mid Y,Layer,Rotation\n";

// Dialog options (defaults requested by user).
int opt_include_through_hole = 1;
int opt_exclude_dnp = 1;
int opt_group_bom = 1;
int opt_export_bom = 1;
int opt_export_cpl = 1;
int opt_extra_bom_cols = 1;   // add Part Number + Quantity columns to BOM
int opt_run_cam = 1;          // also fire the CAM job (Gerbers + drill) on export
string opt_cam_file = "";     // path to the .cam job template
string opt_file_base = "";    // output file base name (default: project/folder name)
int opt_assembly_pdf = 0;     // also print top/bottom assembly PDF via the PRINT command
string opt_asm_top_layers = "20 100";   // layers shown for the TOP assembly PDF
string opt_asm_bot_layers = "20 101";   // layers shown for the BOTTOM assembly PDF
string opt_print_scale = "";  // PRINT scale factor (blank = fit to page)
int opt_split_cpl = 0;   // nice-to-have
int opt_debug_csv = 0;   // nice-to-have
string opt_output_dir = "";

// Warning store.
string warnings[];
int warning_count = 0;

// Geometry scratch values (set by calculate_centroid()).
int geom_has_smd = 0;
int geom_has_pad = 0;
int geom_has_contact = 0;
int geom_used_origin = 0;
real geom_mid_x_mm = 0.0;
real geom_mid_y_mm = 0.0;

// Exported part arrays.
string part_ref[];
string part_ref_key[];
string part_comment[];
string part_comment_norm[];
string part_footprint[];
string part_lcsc[];
string part_mpn[];
string part_layer[];
real part_mid_x_mm[];
real part_mid_y_mm[];
real part_angle_raw[];
real part_angle_corr[];
real part_angle_final[];
int part_has_smd[];
int part_has_pad[];
int part_used_origin[];
int part_count = 0;

// Per-element scratch variables.
string tmp_ref_key;
int tmp_marked_dnp;
string tmp_fp_name;
string tmp_bom_comment;
string tmp_lcsc;
string tmp_mpn;
real tmp_corr;
real tmp_final;

// Sorted row/index buffers (global to avoid array-argument portability issues).
int natural_order[];
string bom_row_comment[];
string bom_row_refs[];
string bom_row_footprint[];
string bom_row_lcsc[];
string bom_row_mpn[];
int bom_row_qty[];
int bom_row_count = 0;

// Summary counters.
int missing_lcsc_count = 0;
int excluded_dnp_count = 0;

// Export summary values.
int report_bom_rows = 0;
int report_cpl_rows = 0;
string report_bom_path = "";
string report_cpl_path = "";

// ----- string helpers -----

string trim_text(string s) {
  while (s && strlen(s) > 0 && isspace(s[0])) s = strsub(s, 1);
  while (s && strlen(s) > 0 && isspace(s[strlen(s) - 1])) s = strsub(s, 0, strlen(s) - 1);
  return s;
}

string collapse_spaces(string s) {
  string out;
  string one;
  int prev_space = 0;
  for (int i = 0; i < strlen(s); ++i) {
    char c = s[i];
    if (isspace(c)) {
      if (!prev_space) out += " ";
      prev_space = 1;
    }
    else {
      sprintf(one, "%c", c);
      out += one;
      prev_space = 0;
    }
  }
  return trim_text(out);
}

string force_dot_decimal(string s) {
  int p;
  while ((p = strchr(s, ',')) >= 0) s[p] = '.';
  return s;
}

string join_path(string dir, string file) {
  if (dir == "") return file;
  char last = dir[strlen(dir) - 1];
  if (last == '/' || last == '\\') return dir + file;
  return dir + "/" + file;
}

string basename_without_ext(string path) {
  string base = filename(path);
  int dot = strrchr(base, '.');
  if (dot > 0) return strsub(base, 0, dot);
  return base;
}

int looks_like_guid(string name) {
  // Fusion's managed workspace names files with cache ids like
  // brd-613ed8b2-6bdf-46a7-8c1e-277c8fe80fc1 - useless as a file base.
  string s = strlwr(trim_text(name));
  int n = strlen(s);
  if (n == 0) return 0;
  if (strstr(s, "brd-") == 0) return 1;
  if (strstr(s, "sch-") == 0) return 1;
  if (strstr(s, "lbr-") == 0) return 1;
  int dashes = 0;
  int other = 0;
  for (int i = 0; i < n; ++i) {
    char c = s[i];
    if (c == '-') ++dashes;
    else if (!((c >= '0' && c <= '9') || (c >= 'a' && c <= 'f'))) ++other;
  }
  if (n >= 32 && other == 0 && dashes >= 3) return 1;
  return 0;
}

string default_file_base(string board_path) {
  // Prefer the containing-folder name (often the project name); fall back to the
  // board file name. Both can be a Fusion cache id (brd-...), which we reject in
  // favour of a clean, editable default.
  string d = filedir(board_path);
  while (strlen(d) > 0 && (d[strlen(d) - 1] == '/' || d[strlen(d) - 1] == '\\'))
    d = strsub(d, 0, strlen(d) - 1);
  int p = strrchr(d, '/');
  int q = strrchr(d, '\\');
  if (q > p) p = q;
  string folder = d;
  if (p >= 0) folder = strsub(d, p + 1);
  folder = trim_text(folder);
  if (folder != "" && !looks_like_guid(folder)) return folder;

  string fb = trim_text(basename_without_ext(board_path));
  if (fb != "" && !looks_like_guid(fb)) return fb;

  return "PCB";
}

int trailing_version_num(string s) {
  int len = strlen(s);
  int dend = len;
  int dstart = len;
  int vpos;
  char vc;
  char sep;

  if (len <= 0) return -1;
  while (dstart > 0 && isdigit(s[dstart - 1])) --dstart;
  if (dstart == dend) return -1; // no trailing digits
  if (dstart <= 0) return -1;
  vpos = dstart - 1;
  vc = s[vpos];
  if (vc != 'V' && vc != 'v') return -1;
  if (vpos > 0) {
    sep = s[vpos - 1];
    if (sep != '_' && sep != '-' && sep != ' ') return -1;
  }

  vpos = strtol(strsub(s, dstart, dend));
  if (vpos <= 0) return -1;
  return vpos;
}

string strip_trailing_version(string s) {
  int len = strlen(s);
  int dstart = len;
  int vpos;
  char sep;
  char vc;

  while (dstart > 0 && isdigit(s[dstart - 1])) --dstart;
  if (dstart == len) return s; // no trailing digits
  if (dstart <= 0) return s;
  vpos = dstart - 1;
  vc = s[vpos];
  if (vc != 'V' && vc != 'v') return s;
  if (vpos > 0) {
    sep = s[vpos - 1];
    if (sep != '_' && sep != '-' && sep != ' ') return s;
  }

  // remove optional separator before 'V'
  if (vpos > 0 && (s[vpos - 1] == '_' || s[vpos - 1] == '-' || s[vpos - 1] == ' ')) --vpos;
  return strsub(s, 0, vpos);
}

int version_from_export_filename(string fname, string root) {
  string up_fname;
  string up_root;
  string marker;
  int pos;
  int dstart;
  int dend;
  int v;

  up_fname = strupr(fname);
  up_root = strupr(root);
  marker = up_root + "_V";
  pos = strstr(up_fname, marker);
  if (pos < 0) return -1;

  dstart = pos + strlen(marker);
  dend = dstart;
  while (dend < strlen(fname) && isdigit(fname[dend])) ++dend;
  if (dend <= dstart) return -1;
  v = strtol(strsub(fname, dstart, dend));
  if (v <= 0) return -1;
  return v;
}

int latest_export_version_in_dir(string out_dir, string root) {
  string files[];
  string pattern;
  int n;
  int vmax = -1;
  int vcur;

  pattern = join_path(out_dir, root + "_v*_jlc_*.csv");
  n = fileglob(files, pattern);
  for (int i = 0; i < n; ++i) {
    vcur = version_from_export_filename(filename(files[i]), root);
    if (vcur > vmax) vmax = vcur;
  }
  return vmax;
}

string effective_export_base(string board_base, string out_dir) {
  string root;
  string b;
  string sver;
  int board_ver;
  int dir_ver;
  int use_ver;

  b = trim_text(board_base);
  board_ver = trailing_version_num(b);
  if (board_ver >= 0) root = strip_trailing_version(b);
  else root = b;

  dir_ver = latest_export_version_in_dir(out_dir, root);
  use_ver = board_ver;
  if (use_ver < 0) use_ver = dir_ver;
  else if (dir_ver > use_ver) use_ver = dir_ver;

  if (use_ver >= 0) {
    sprintf(sver, "_v%03d", use_ver);
    return root + sver;
  }
  return b;
}

string csv_escape(string s) {
  string out;
  string one;
  int needs_quotes = 0;
  for (int i = 0; i < strlen(s); ++i) {
    char c = s[i];
    if (c == '"' || c == ',' || c == 10 || c == 13) needs_quotes = 1;
    if (c == '"') out += "\"\"";
    else if (c == 10 || c == 13) out += " ";
    else {
      sprintf(one, "%c", c);
      out += one;
    }
  }
  if (needs_quotes) out = "\"" + out + "\"";
  return out;
}

string fmt_mm(real v) {
  string s;
  sprintf(s, "%.4f", v);
  return force_dot_decimal(s);
}

string fmt_deg(real v) {
  string s;
  sprintf(s, "%.3f", v);
  return force_dot_decimal(s);
}

string natural_ref_key(string ref) {
  // Natural ordering key: prefix + zero-padded number + suffix (e.g. C1,C2,C10).
  string s = strupr(trim_text(ref));
  int i = 0;
  while (i < strlen(s) && !isdigit(s[i])) ++i;
  int j = i;
  while (j < strlen(s) && isdigit(s[j])) ++j;
  string prefix = strsub(s, 0, i);
  string digits = strsub(s, i, j);
  string suffix = strsub(s, j);
  int n = 2147483647;
  if (digits != "") n = strtol(digits);
  string key_n;
  sprintf(key_n, "%010d", n);
  return prefix + "|" + key_n + "|" + suffix + "|" + s;
}

// ----- warnings -----

void add_warning(string msg) {
  // Keep warnings unique and deterministic.
  for (int i = 0; i < warning_count; ++i) {
    if (warnings[i] == msg) return;
  }
  warnings[warning_count++] = msg;
}

// ----- attribute helpers -----

int attr_exists_ci(UL_ELEMENT E, string name) {
  string target = strupr(name);
  E.attributes(A) {
    if (strupr(A.name) == target) return 1;
  }
  return 0;
}

string attr_value_ci(UL_ELEMENT E, string name) {
  string target = strupr(name);
  E.attributes(A) {
    if (strupr(A.name) == target) return A.value;
  }
  return "";
}

int looks_numeric(string s) {
  s = trim_text(force_dot_decimal(s));
  if (s == "") return 0;
  int has_digit = 0;
  int i = 0;
  if (s[0] == '+' || s[0] == '-') i = 1;
  for (; i < strlen(s); ++i) {
    char c = s[i];
    if (isdigit(c)) {
      has_digit = 1;
      continue;
    }
    if (c == '.' || c == ' ') continue;
    return 0;
  }
  return has_digit;
}

int value_is_trueish(string raw) {
  string v = strupr(trim_text(raw));
  if (v == "1" || v == "Y" || v == "YES" || v == "TRUE" || v == "ON") return 1;
  return 0;
}

int value_is_noish(string raw) {
  string v = strupr(trim_text(raw));
  if (v == "0" || v == "N" || v == "NO" || v == "FALSE" || v == "OFF") return 1;
  return 0;
}

int contains_ci(string haystack, string needle) {
  string hs;
  string nd;
  if (needle == "") return 1;
  hs = strupr(haystack);
  nd = strupr(needle);
  return strstr(hs, nd) >= 0;
}

int attr_trueish(UL_ELEMENT E, string name) {
  if (!attr_exists_ci(E, name)) return 0;
  return value_is_trueish(attr_value_ci(E, name));
}

int is_jlc_ignored(UL_ELEMENT E) {
  return attr_trueish(E, "JLC_IGNORE");
}

int is_explicit_dnp(UL_ELEMENT E) {
  // DNP filtering supports DNP/DNI/DNS, POPULATE=NO, EXCLUDE_FROM_JLC=1.
  // Additionally, any string containing "DNP" (case-insensitive) marks as DNP.
  if (contains_ci(E.value, "DNP")) return 1;
  E.attributes(A) {
    if (contains_ci(A.name, "DNP")) return 1;
    if (contains_ci(A.value, "DNP")) return 1;
  }
  if (attr_exists_ci(E, "DNP")) return 1;
  if (attr_exists_ci(E, "DNI")) return 1;
  if (attr_exists_ci(E, "DNS")) return 1;
  if (attr_exists_ci(E, "POPULATE") && value_is_noish(attr_value_ci(E, "POPULATE"))) return 1;
  if (attr_trueish(E, "EXCLUDE_FROM_JLC")) return 1;
  return 0;
}

int is_virtual_part(UL_ELEMENT E) {
  if (!attr_exists_ci(E, "VIRTUAL")) return 0;
  string v = trim_text(attr_value_ci(E, "VIRTUAL"));
  if (v == "") return 1;
  if (value_is_noish(v)) return 0;
  return 1;
}

string lcsc_part_number(UL_ELEMENT E) {
  // First non-empty value in required priority order.
  string v;
  v = trim_text(attr_value_ci(E, "LCSC_PART")); if (v != "") return v;
  v = trim_text(attr_value_ci(E, "LCSC")); if (v != "") return v;
  v = trim_text(attr_value_ci(E, "LCSC_PN")); if (v != "") return v;
  v = trim_text(attr_value_ci(E, "JLCPCB_PART")); if (v != "") return v;
  v = trim_text(attr_value_ci(E, "LCSC_PART_NUMBER")); if (v != "") return v;
  return "";
}

string mpn_part_number(UL_ELEMENT E) {
  // Manufacturer part number: first non-empty value across common attribute names.
  string v;
  v = trim_text(attr_value_ci(E, "MPN")); if (v != "") return v;
  v = trim_text(attr_value_ci(E, "PART_NUMBER")); if (v != "") return v;
  v = trim_text(attr_value_ci(E, "PART NUMBER")); if (v != "") return v;
  v = trim_text(attr_value_ci(E, "PARTNUMBER")); if (v != "") return v;
  v = trim_text(attr_value_ci(E, "PART_NO")); if (v != "") return v;
  v = trim_text(attr_value_ci(E, "PARTNO")); if (v != "") return v;
  v = trim_text(attr_value_ci(E, "PART#")); if (v != "") return v;
  v = trim_text(attr_value_ci(E, "MANUFACTURER_PART_NUMBER")); if (v != "") return v;
  v = trim_text(attr_value_ci(E, "MANUFACTURER PART NUMBER")); if (v != "") return v;
  v = trim_text(attr_value_ci(E, "MFR_PART_NUMBER")); if (v != "") return v;
  v = trim_text(attr_value_ci(E, "MFG_PART_NUMBER")); if (v != "") return v;
  v = trim_text(attr_value_ci(E, "MFR_PN")); if (v != "") return v;
  v = trim_text(attr_value_ci(E, "MFR#")); if (v != "") return v;
  return "";
}

string bom_comment_for(UL_ELEMENT E) {
  string v = trim_text(attr_value_ci(E, "BOM_COMMENT"));
  if (v != "") return v;
  v = trim_text(E.value);
  if (v != "") return v;
  v = trim_text(E.package.name);
  if (v != "") return v;
  return E.name;
}

string normalized_comment_key(string comment) {
  return strupr(collapse_spaces(comment));
}

string footprint_for(UL_ELEMENT E) {
  string p = trim_text(E.package.name);
  return p;
}

real jlc_rotation_correction(UL_ELEMENT E) {
  string raw = trim_text(attr_value_ci(E, "JLC_ROTATION"));
  if (raw == "") return 0.0;
  if (!looks_numeric(raw)) {
    add_warning("Invalid JLC_ROTATION on " + E.name + ": '" + raw + "' (ignored)");
    return 0.0;
  }
  real v = strtod(force_dot_decimal(raw));
  if (v < -10000.0 || v > 10000.0) {
    add_warning("Obviously invalid JLC_ROTATION on " + E.name + ": '" + raw + "' (ignored)");
    return 0.0;
  }
  return v;
}

// ----- geometry & rotation -----

void calculate_centroid(UL_ELEMENT E) {
  // Centroid strategy:
  // 1) Use placed package contact coordinates (pads/SMDs) in board space.
  // 2) Compute center of contact bounding box (manufacturing-friendly center).
  // 3) Fallback to element origin only if no contacts exist.
  int xmin = 2147483647;
  int ymin = 2147483647;
  int xmax = -2147483647;
  int ymax = -2147483647;

  geom_has_smd = 0;
  geom_has_pad = 0;
  geom_has_contact = 0;
  geom_used_origin = 0;

  E.package.contacts(C) {
    if (C.smd) geom_has_smd = 1;
    if (C.pad) geom_has_pad = 1;
    if (C.smd || C.pad) {
      geom_has_contact = 1;
      if (C.x < xmin) xmin = C.x;
      if (C.y < ymin) ymin = C.y;
      if (C.x > xmax) xmax = C.x;
      if (C.y > ymax) ymax = C.y;
    }
  }

  if (geom_has_contact) {
    geom_mid_x_mm = u2mm((xmin + xmax) / 2);
    geom_mid_y_mm = u2mm((ymin + ymax) / 2);
  }
  else {
    geom_mid_x_mm = u2mm(E.x);
    geom_mid_y_mm = u2mm(E.y);
    geom_used_origin = 1;
  }
}

real normalize_rotation(real angle) {
  while (angle < 0.0) angle += 360.0;
  while (angle >= 360.0) angle -= 360.0;
  return angle;
}

real final_rotation(real angle_raw, int is_bottom, real correction) {
  // Bottom-side mirror handling:
  // Eagle stores mirrored parts with an angle plus mirror flag.
  // For placement rotation, mirrored orientation reverses angular direction,
  // so convert with (360 - angle), then add optional JLC_ROTATION.
  real base = angle_raw;
  if (is_bottom) base = 360.0 - base;
  return normalize_rotation(base + correction);
}

int coord_is_reasonable(real x_mm, real y_mm) {
  if (x_mm < -100000.0 || x_mm > 100000.0) return 0;
  if (y_mm < -100000.0 || y_mm > 100000.0) return 0;
  return 1;
}

// ----- output helpers -----

void write_cpl(string path) {
  output(path, "wt") {
    printf("%s", CPL_HEADER);
    for (int i = 0; i < part_count; ++i) {
      int p = natural_order[i];
      printf("%s,%s,%s,%s,%s\n",
             csv_escape(part_ref[p]),
             csv_escape(fmt_mm(part_mid_x_mm[p])),
             csv_escape(fmt_mm(part_mid_y_mm[p])),
             csv_escape(part_layer[p]),
             csv_escape(fmt_deg(part_angle_final[p])));
    }
  }
}

void write_cpl_side(string path, string side) {
  output(path, "wt") {
    printf("%s", CPL_HEADER);
    for (int i = 0; i < part_count; ++i) {
      int p = natural_order[i];
      if (part_layer[p] != side) continue;
      printf("%s,%s,%s,%s,%s\n",
             csv_escape(part_ref[p]),
             csv_escape(fmt_mm(part_mid_x_mm[p])),
             csv_escape(fmt_mm(part_mid_y_mm[p])),
             csv_escape(part_layer[p]),
             csv_escape(fmt_deg(part_angle_final[p])));
    }
  }
}

int build_bom_rows(int grouped) {
  int rows = 0;
  int i;
  int p;
  int g;
  int existing;
  int group_count = 0;
  string gkey;
  string group_keys[];

  if (part_count <= 0) return 0;
  if (!grouped) {
    for (i = 0; i < part_count; ++i) {
      p = natural_order[i];
      bom_row_comment[rows] = part_comment[p];
      bom_row_refs[rows] = part_ref[p];
      bom_row_footprint[rows] = part_footprint[p];
      bom_row_lcsc[rows] = part_lcsc[p];
      bom_row_mpn[rows] = part_mpn[p];
      bom_row_qty[rows] = 1;
      ++rows;
    }
    return rows;
  }

  // Group key: normalized comment/value + footprint + LCSC Part #.
  // We iterate already-natural-sorted refs, so each group's designator list is deterministic.
  for (i = 0; i < part_count; ++i) {
    p = natural_order[i];
    gkey = part_comment_norm[p] + "\t" + strupr(part_footprint[p]) + "\t" + strupr(part_lcsc[p]);
    existing = -1;

    for (g = 0; g < group_count; ++g) {
      if (group_keys[g] == gkey) {
        existing = g;
        break;
      }
    }

    if (existing < 0) {
      existing = group_count;
      group_keys[group_count] = gkey;
      bom_row_comment[group_count] = part_comment[p];
      bom_row_refs[group_count] = part_ref[p];
      bom_row_footprint[group_count] = part_footprint[p];
      bom_row_lcsc[group_count] = part_lcsc[p];
      bom_row_mpn[group_count] = part_mpn[p];
      bom_row_qty[group_count] = 1;
      ++group_count;
    }
    else {
      bom_row_refs[existing] += "," + part_ref[p];
      bom_row_qty[existing] += 1;
    }
  }
  return group_count;
}

void write_bom(string path, int row_count) {
  output(path, "wt") {
    if (opt_extra_bom_cols) printf("%s", BOM_HEADER_EXT);
    else                    printf("%s", BOM_HEADER);
    for (int i = 0; i < row_count; ++i) {
      if (opt_extra_bom_cols) {
        printf("%s,%s,%s,%s,%s,%d\n",
               csv_escape(bom_row_comment[i]),
               csv_escape(bom_row_refs[i]),
               csv_escape(bom_row_footprint[i]),
               csv_escape(bom_row_lcsc[i]),
               csv_escape(bom_row_mpn[i]),
               bom_row_qty[i]);
      }
      else {
        printf("%s,%s,%s,%s\n",
               csv_escape(bom_row_comment[i]),
               csv_escape(bom_row_refs[i]),
               csv_escape(bom_row_footprint[i]),
               csv_escape(bom_row_lcsc[i]));
      }
    }
  }
}

void write_warning_log(string path) {
  output(path, "wt") {
    for (int i = 0; i < warning_count; ++i) printf("%s\n", warnings[i]);
  }
}

void write_debug_csv(string path) {
  output(path, "wt") {
    printf("Designator,Layer,Has SMD,Has PAD,Centroid Source,Mid X,Mid Y,Angle Raw,JLC_ROTATION,Angle Final,Footprint,LCSC Part #\n");
    for (int i = 0; i < part_count; ++i) {
      int p = natural_order[i];
      string centroid_src = "CONTACT_BBOX";
      if (part_used_origin[p]) centroid_src = "ORIGIN_FALLBACK";
      printf("%s,%s,%d,%d,%s,%s,%s,%s,%s,%s,%s,%s\n",
             csv_escape(part_ref[p]),
             csv_escape(part_layer[p]),
             part_has_smd[p],
             part_has_pad[p],
             csv_escape(centroid_src),
             csv_escape(fmt_mm(part_mid_x_mm[p])),
             csv_escape(fmt_mm(part_mid_y_mm[p])),
             csv_escape(fmt_deg(part_angle_raw[p])),
             csv_escape(fmt_deg(part_angle_corr[p])),
             csv_escape(fmt_deg(part_angle_final[p])),
             csv_escape(part_footprint[p]),
             csv_escape(part_lcsc[p]));
    }
  }
}

// ----- dialog -----

int show_export_dialog() {
  return dlgDialog("JLCPCB BOM/CPL Export") {
    dlgVBoxLayout {
      dlgLabel("Output folder");
      dlgHBoxLayout {
        dlgStringEdit(opt_output_dir);
        dlgPushButton("Browse...") {
          string picked = dlgDirectory("Select output folder", opt_output_dir);
          if (picked != "") opt_output_dir = picked;
        }
      }
      dlgLabel("Output file base name");
      dlgStringEdit(opt_file_base);
      dlgLabel("CAM job template (.cam)");
      dlgHBoxLayout {
        dlgStringEdit(opt_cam_file);
        dlgPushButton("Browse...") {
          string start_cam = opt_cam_file;
          if (trim_text(start_cam) == "") start_cam = opt_output_dir;
          string picked_cam = dlgFileOpen("Select CAM job", start_cam, "*.cam");
          if (picked_cam != "") opt_cam_file = picked_cam;
        }
      }
      dlgCheckBox("Export BOM", opt_export_bom);
      dlgCheckBox("Export CPL", opt_export_cpl);
      dlgCheckBox("Run CAM job (Gerbers + drill) into the same folder", opt_run_cam);
      dlgCheckBox("Also print assembly PDF (top/bottom)", opt_assembly_pdf);
      dlgLabel("Assembly PDF layers  (top / bottom)");
      dlgHBoxLayout {
        dlgStringEdit(opt_asm_top_layers);
        dlgStringEdit(opt_asm_bot_layers);
      }
      dlgLabel("Print scale  (blank = fit to page)");
      dlgStringEdit(opt_print_scale);
      dlgCheckBox("Include through-hole parts", opt_include_through_hole);
      dlgCheckBox("Exclude DNP parts", opt_exclude_dnp);
      dlgCheckBox("Group BOM rows", opt_group_bom);
      dlgCheckBox("Add Part Number + Quantity columns", opt_extra_bom_cols);
      dlgCheckBox("Export separate Top/Bottom CPL (optional)", opt_split_cpl);
      dlgCheckBox("Export debug CSV (optional)", opt_debug_csv);
      dlgHBoxLayout {
        dlgStretch(1);
        dlgPushButton("+Export") {
          if (trim_text(opt_output_dir) == "") dlgMessageBox("Choose an output folder.");
          else if (!opt_export_bom && !opt_export_cpl && !opt_run_cam) dlgMessageBox("Select at least one output: BOM, CPL, or CAM job.");
          else if (opt_run_cam && trim_text(opt_cam_file) == "") dlgMessageBox("Choose a .cam job file, or uncheck 'Run CAM job'.");
          else dlgAccept();
        }
        dlgPushButton("-Cancel") dlgReject();
      }
    }
  };
}

// ----- main -----

if (!board) {
  dlgMessageBox("Run this ULP from a board editor window.");
  exit(0);
}

board(B) {
  // Default the file base name to the project/folder name (editable in the dialog).
  if (trim_text(opt_file_base) == "") opt_file_base = default_file_base(B.name);

  // Headless mode for script orchestration:
  //   RUN fusion_jlc_export.ulp "<output_folder>" ["<cam_file>"]
  // skips the dialog and exports BOM+CPL with default options into that folder.
  if (argc > 1) {
    opt_output_dir = trim_text(argv[1]);
    if (argc > 2) opt_cam_file = trim_text(argv[2]);
  }
  else {
    // Start browsing from the folder where this ULP lives; fall back to board dir.
    string ulp_dir = filedir(argv[0]);
    if (trim_text(ulp_dir) != "") opt_output_dir = ulp_dir;
    else opt_output_dir = filedir(B.name);
    if (!show_export_dialog()) exit(0);
  }

  string seen_refs[];
  int seen_ref_count = 0;

  // Extract all fitted parts from board with deterministic filtering.
  B.elements(E) {
    tmp_ref_key = strupr(trim_text(E.name));

    for (int i = 0; i < seen_ref_count; ++i) {
      if (seen_refs[i] == tmp_ref_key) {
        add_warning("Duplicate reference designator: " + E.name);
        break;
      }
    }
    seen_refs[seen_ref_count++] = tmp_ref_key;

    if (is_jlc_ignored(E)) {
      ++excluded_dnp_count;
      continue;
    }
    if (is_virtual_part(E)) continue;

    tmp_marked_dnp = 0;
    if (!E.populate) tmp_marked_dnp = 1;
    if (is_explicit_dnp(E)) tmp_marked_dnp = 1;
    if (opt_exclude_dnp && tmp_marked_dnp) {
      ++excluded_dnp_count;
      continue;
    }

    calculate_centroid(E);

    // Exclude non-placeable packages that have no SMD/PAD contacts
    // (e.g. silkscreen-only/mechanical graphics-only footprints).
    if (!geom_has_contact) continue;

    // If through-hole exclusion is enabled, drop pure pad-only parts.
    if (!opt_include_through_hole && geom_has_pad && !geom_has_smd) continue;

    tmp_fp_name = footprint_for(E);
    if (trim_text(tmp_fp_name) == "") {
      add_warning("Missing package/footprint name on " + E.name);
      tmp_fp_name = "";
    }

    if (geom_used_origin) {
      add_warning("No contact-based centroid on " + E.name + ", using element origin.");
    }
    if (!coord_is_reasonable(geom_mid_x_mm, geom_mid_y_mm)) {
      add_warning("No valid board coordinate on " + E.name + " (using computed fallback).");
    }

    tmp_bom_comment = bom_comment_for(E);
    tmp_lcsc = lcsc_part_number(E);
    tmp_mpn = mpn_part_number(E);
    if (tmp_lcsc == "") {
      ++missing_lcsc_count;
    }

    tmp_corr = jlc_rotation_correction(E);
    tmp_final = final_rotation(E.angle, E.mirror, tmp_corr);
    if (tmp_final < 0.0 || tmp_final >= 360.0) {
      add_warning("Invalid normalized rotation on " + E.name + " (" + fmt_deg(tmp_final) + ")");
      tmp_final = normalize_rotation(tmp_final);
    }

    part_ref[part_count] = E.name;
    part_ref_key[part_count] = natural_ref_key(E.name);
    part_comment[part_count] = tmp_bom_comment;
    part_comment_norm[part_count] = normalized_comment_key(tmp_bom_comment);
    part_footprint[part_count] = tmp_fp_name;
    part_lcsc[part_count] = tmp_lcsc;
    part_mpn[part_count] = tmp_mpn;
    part_layer[part_count] = "Top";
    if (E.mirror) part_layer[part_count] = "Bottom";
    part_mid_x_mm[part_count] = geom_mid_x_mm;
    part_mid_y_mm[part_count] = geom_mid_y_mm;
    part_angle_raw[part_count] = E.angle;
    part_angle_corr[part_count] = tmp_corr;
    part_angle_final[part_count] = tmp_final;
    part_has_smd[part_count] = geom_has_smd;
    part_has_pad[part_count] = geom_has_pad;
    part_used_origin[part_count] = geom_used_origin;
    ++part_count;
  }

  for (int n = 0; n < part_count; ++n) natural_order[n] = n;
  if (part_count > 1) sort(part_count, natural_order, part_ref_key);

  string base;
  if (trim_text(opt_file_base) != "") base = trim_text(opt_file_base);
  else base = effective_export_base(basename_without_ext(B.name), opt_output_dir);
  string bom_path = join_path(opt_output_dir, base + "_jlc_bom.csv");
  string cpl_path = join_path(opt_output_dir, base + "_jlc_cpl.csv");
  string top_cpl_path = join_path(opt_output_dir, base + "_jlc_cpl_top.csv");
  string bottom_cpl_path = join_path(opt_output_dir, base + "_jlc_cpl_bottom.csv");
  string debug_path = join_path(opt_output_dir, base + "_jlc_debug.csv");
  string warn_path = join_path(opt_output_dir, base + "_jlc_warnings.txt");

  report_bom_rows = 0;
  report_cpl_rows = 0;
  report_bom_path = "(not exported)";
  report_cpl_path = "(not exported)";

  if (opt_export_cpl) {
    write_cpl(cpl_path);
    report_cpl_rows = part_count;
    report_cpl_path = cpl_path;
    if (opt_split_cpl) {
      write_cpl_side(top_cpl_path, "Top");
      write_cpl_side(bottom_cpl_path, "Bottom");
    }
  }

  if (opt_export_bom) {
    bom_row_count = build_bom_rows(opt_group_bom);
    write_bom(bom_path, bom_row_count);
    report_bom_rows = bom_row_count;
    report_bom_path = bom_path;
  }

  if (warning_count > 0) write_warning_log(warn_path);
  if (opt_debug_csv) write_debug_csv(debug_path);

  string summary;
  sprintf(summary,
          "Export complete.\n\n"
          "Total fitted parts exported: %d\n"
          "BOM rows: %d\n"
          "CPL rows: %d\n"
          "Missing LCSC Part #: %d\n"
          "Excluded DNP parts: %d\n"
          "Warnings: %d\n\n"
          "BOM: %s\n"
          "CPL: %s",
          part_count, report_bom_rows, report_cpl_rows, missing_lcsc_count, excluded_dnp_count, warning_count, report_bom_path, report_cpl_path);

  if (opt_export_cpl && opt_split_cpl) summary += "\nTop CPL: " + top_cpl_path + "\nBottom CPL: " + bottom_cpl_path;
  if (opt_debug_csv) summary += "\nDebug CSV: " + debug_path;
  if (warning_count > 0) summary += "\nWarning log: " + warn_path;

  if (argc <= 1) dlgMessageBox(summary);

  // Hand manufacturing steps to the editor via a generated script, run on exit
  // (CSVs are already written by now). The script is left on disk for inspection.
  //  - Gerbers/drill : MANUFACTURING EXPORT to a .zip -> <base>_gerbers.zip
  //  - Assembly PDF  : printed with PRINT, because CAM *image* outputs are NOT
  //    produced in automation/script mode (known Fusion limitation).
  int want_cam = (opt_run_cam && trim_text(opt_cam_file) != "");
  if (want_cam || opt_assembly_pdf) {
    string gerber_zip = join_path(opt_output_dir, base + "_gerbers.zip");
    string top_pdf    = join_path(opt_output_dir, base + "_assembly_top.pdf");
    string bot_pdf    = join_path(opt_output_dir, base + "_assembly_bottom.pdf");
    string scr_path   = join_path(opt_output_dir, base + "_run.scr");
    string psfx = "";
    if (trim_text(opt_print_scale) != "") psfx = " " + trim_text(opt_print_scale);
    output(scr_path, "wt") {
      printf("SET CONFIRM YES;\n");
      printf("WRITE;\n");
      if (want_cam)
        printf("MANUFACTURING EXPORT '%s' '%s';\n", gerber_zip, opt_cam_file);
      if (opt_assembly_pdf) {
        printf("DISPLAY NONE;\n");
        printf("DISPLAY %s;\n", opt_asm_top_layers);
        printf("PRINT FILE '%s' PAPER A4 LANDSCAPE BLACK SOLID -CAPTION%s;\n", top_pdf, psfx);
        printf("DISPLAY NONE;\n");
        printf("DISPLAY %s;\n", opt_asm_bot_layers);
        printf("PRINT FILE '%s' PAPER A4 LANDSCAPE BLACK SOLID -CAPTION%s;\n", bot_pdf, psfx);
      }
    }
    exit("SCRIPT '" + scr_path + "';");
  }
}
